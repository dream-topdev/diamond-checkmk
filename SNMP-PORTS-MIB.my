--
-- SNMP-PORTS-MIB.my
-- MIB generated by MG-SOFT Visual MIB Builder Version 6.0  Build 88
-- Friday, May 28, 2021 at 17:10:41
--

-- 
-- 

	SNMP-PORTS-MIB DEFINITIONS ::= BEGIN
 
		IMPORTS
			OBJECT-GROUP			
				FROM SNMPv2-CONF			
			enterprises, Integer32, OBJECT-TYPE, MODULE-IDENTITY			
				FROM SNMPv2-SMI;
	
	
		-- 1.3.6.1.4.1.91111.4.80.11
		swPorts MODULE-IDENTITY 
			LAST-UPDATED "202105201345Z"		-- May 20, 2021 at 13:45 GMT
			ORGANIZATION 
				"Organization."
			CONTACT-INFO 
				"Contact-info."
			DESCRIPTION 
				"Description."
			::= { dumont 11 }

		
	
--
-- Node definitions
--
	
		-- 1.3.6.1.4.1.91111
		custom OBJECT IDENTIFIER ::= { enterprises 91111 }

		
		-- 1.3.6.1.4.1.91111.4
		radio OBJECT IDENTIFIER ::= { custom 4 }

		
		-- 1.3.6.1.4.1.91111.4.80
		dumont OBJECT IDENTIFIER ::= { radio 80 }

		
		-- 1.3.6.1.4.1.91111.4.80.11.1
		swPortsObjects OBJECT IDENTIFIER ::= { swPorts 1 }

		
		-- 1.3.6.1.4.1.91111.4.80.11.1.2
		portConfigTable OBJECT-TYPE
			SYNTAX SEQUENCE OF PortConfigEntry
			MAX-ACCESS not-accessible
			STATUS current
			DESCRIPTION
				"Description."
			::= { swPortsObjects 2 }

		
		-- 1.3.6.1.4.1.91111.4.80.11.1.2.1
		portConfigEntry OBJECT-TYPE
			SYNTAX PortConfigEntry
			MAX-ACCESS not-accessible
			STATUS current
			DESCRIPTION
				"Description."
			INDEX { swPortIndex }
			::= { portConfigTable 1 }

		
		PortConfigEntry ::=
			SEQUENCE { 
				swPortIndex
					Integer32,
				portLink
					INTEGER,
				portSpeedCurrent
					OCTET STRING,
				portSpeed
					INTEGER,
				portFlowctrlEnable
					INTEGER,
				portFlowctrlRxCur
					INTEGER,
				portFlowctrlTxCur
					INTEGER
			 }

		-- 1.3.6.1.4.1.91111.4.80.11.1.2.1.1
		swPortIndex OBJECT-TYPE
			SYNTAX Integer32 (1..10)
			MAX-ACCESS read-only
			STATUS current
			DESCRIPTION
				"Description."
			::= { portConfigEntry 1 }

		
		-- 1.3.6.1.4.1.91111.4.80.11.1.2.1.2
		portLink OBJECT-TYPE
			SYNTAX INTEGER
				{
				linkdown(0),
				linkup(1)
				}
			MAX-ACCESS read-only
			STATUS current
			DESCRIPTION
				"Description."
			::= { portConfigEntry 2 }

		
		-- 1.3.6.1.4.1.91111.4.80.11.1.2.1.3
		portSpeedCurrent OBJECT-TYPE
			SYNTAX OCTET STRING
			MAX-ACCESS read-only
			STATUS current
			DESCRIPTION
				"Description."
			::= { portConfigEntry 3 }

		
		-- 1.3.6.1.4.1.91111.4.80.11.1.2.1.4
		portSpeed OBJECT-TYPE
			SYNTAX INTEGER
				{
				speedundefined(0),
				speed10m(1),
				speed100m(2),
				speed1000m(3),
				speed2500m(4),
				speed5000m(5),
				speed10g(6)
				}
			MAX-ACCESS read-only
			STATUS current
			DESCRIPTION
				"Description."
			::= { portConfigEntry 4 }

		
		-- 1.3.6.1.4.1.91111.4.80.11.1.2.1.5
		portFlowctrlEnable OBJECT-TYPE
			SYNTAX INTEGER
				{
				disabled(0),
				enabled(1)
				}
			MAX-ACCESS read-write
			STATUS current
			DESCRIPTION
				"Description."
			::= { portConfigEntry 5 }

		
		-- 1.3.6.1.4.1.91111.4.80.11.1.2.1.6
		portFlowctrlRxCur OBJECT-TYPE
			SYNTAX INTEGER
				{
				disabled(0),
				enabled(1)
				}
			MAX-ACCESS read-only
			STATUS current
			DESCRIPTION
				"Description."
			::= { portConfigEntry 6 }

		
		-- 1.3.6.1.4.1.91111.4.80.11.1.2.1.7
		portFlowctrlTxCur OBJECT-TYPE
			SYNTAX INTEGER
				{
				disabled(0),
				enabled(1)
				}
			MAX-ACCESS read-only
			STATUS current
			DESCRIPTION
				"Description."
			::= { portConfigEntry 7 }

		
		-- 1.3.6.1.4.1.91111.4.80.11.2
		swPortStatisticesGroups OBJECT IDENTIFIER ::= { swPorts 2 }

		
		-- 1.3.6.1.4.1.91111.4.80.11.2.1
		swPortStatisticesGroup OBJECT-GROUP
			OBJECTS { swPortIndex, portLink, portSpeedCurrent, portSpeed, portFlowctrlEnable, 
				portFlowctrlRxCur, portFlowctrlTxCur }
			STATUS current
			DESCRIPTION 
				"Description."
			::= { swPortStatisticesGroups 1 }

		
	
	END

--
-- SNMP-PORTS-MIB.my
--
