--
-- RADIO-DUMONTSTATUS-MIB.my
-- MIB generated by MG-SOFT Visual MIB Builder Version 6.0  Build 88
-- Friday, May 14, 2021 at 12:04:17
--

-- 
-- 

	RADIO-DUMONTSTATUS-MIB DEFINITIONS ::= BEGIN
 
		IMPORTS
			OBJECT-GROUP			
				FROM SNMPv2-CONF			
			enterprises, Integer32, OBJECT-TYPE, MODULE-IDENTITY			
				FROM SNMPv2-SMI			
			TEXTUAL-CONVENTION			
				FROM SNMPv2-TC;
	
	
		-- 1.3.6.1.4.1.91111.4.80.1
		radioStatus MODULE-IDENTITY 
			LAST-UPDATED "202105121345Z"		-- May 12, 2021 at 13:45 GMT
			ORGANIZATION 
				"Organization."
			CONTACT-INFO 
				"Contact-info."
			DESCRIPTION 
				"Description."
			::= { dumont 1 }

		
	
--
-- Type definitions
--
	
		ModulationType ::= INTEGER
			{
			qpsk(0),
			qam16(1),
			qam32(2),
			qam64(3),
			qam128(4),
			qam256(5),
			qam512(6),
			qam1024(7),
			qam2048(8),
			qam4096(9),
			acm(10),
			acmm(11)
			}

	
--
-- Textual conventions
--
	
		TempertureTC ::= TEXTUAL-CONVENTION
			DISPLAY-HINT 
				"d-1"
			STATUS current
			DESCRIPTION 
				"Description."
			SYNTAX Integer32

		RslTC ::= TEXTUAL-CONVENTION
			DISPLAY-HINT 
				"d-1"
			STATUS current
			DESCRIPTION 
				"Description."
			SYNTAX Integer32

		SnrTc ::= TEXTUAL-CONVENTION
			DISPLAY-HINT 
				"d-1"
			STATUS current
			DESCRIPTION 
				"Description."
			SYNTAX Integer32

	
--
-- Node definitions
--
	
		-- 1.3.6.1.4.1.91111
		custom OBJECT IDENTIFIER ::= { enterprises 91111 }

		
		-- 1.3.6.1.4.1.91111.4
		radio OBJECT IDENTIFIER ::= { custom 4 }

		
		-- 1.3.6.1.4.1.91111.4.80
		dumont OBJECT IDENTIFIER ::= { radio 80 }

		
		-- 1.3.6.1.4.1.91111.4.80.1.1
		radiolStatusObjects OBJECT IDENTIFIER ::= { radioStatus 1 }

		
		-- 1.3.6.1.4.1.91111.4.80.1.1.1
		generalStatusTable OBJECT-TYPE
			SYNTAX SEQUENCE OF GeneralStatusEntry
			MAX-ACCESS not-accessible
			STATUS current
			DESCRIPTION
				"Description."
			::= { radiolStatusObjects 1 }

		
		-- 1.3.6.1.4.1.91111.4.80.1.1.1.1
		generalStatusEntry OBJECT-TYPE
			SYNTAX GeneralStatusEntry
			MAX-ACCESS not-accessible
			STATUS current
			DESCRIPTION
				"Description."
			INDEX { generalStatusIndex }
			::= { generalStatusTable 1 }

		
		GeneralStatusEntry ::=
			SEQUENCE { 
				generalStatusIndex
					Integer32,
				generalStatuslocation
					OCTET STRING,
				ipStatus
					OCTET STRING,
				temperture
					TempertureTC,
				tr1RSSI
					Integer32,
				tr2RSSI
					Integer32,
				xpicMode
					INTEGER,
				siteName
					OCTET STRING,
				systemUptime
					OCTET STRING,
				mcuUptime
					OCTET STRING,
				systemAlarm
					INTEGER
			 }

		-- 1.3.6.1.4.1.91111.4.80.1.1.1.1.1
		generalStatusIndex OBJECT-TYPE
			SYNTAX Integer32 (1..2)
			MAX-ACCESS read-only
			STATUS current
			DESCRIPTION
				"1,local  2 remote."
			::= { generalStatusEntry 1 }

		
		-- 1.3.6.1.4.1.91111.4.80.1.1.1.1.2
		generalStatuslocation OBJECT-TYPE
			SYNTAX OCTET STRING
			MAX-ACCESS read-only
			STATUS current
			DESCRIPTION
				"display local or remote."
			::= { generalStatusEntry 2 }

		
		-- 1.3.6.1.4.1.91111.4.80.1.1.1.1.3
		ipStatus OBJECT-TYPE
			SYNTAX OCTET STRING
			MAX-ACCESS read-only
			STATUS current
			DESCRIPTION
				"Description."
			::= { generalStatusEntry 3 }

		
		-- 1.3.6.1.4.1.91111.4.80.1.1.1.1.4
		temperture OBJECT-TYPE
			SYNTAX TempertureTC
			MAX-ACCESS read-only
			STATUS current
			DESCRIPTION
				"The real temperature value needs to be divided by 10."
			::= { generalStatusEntry 4 }

		
		-- 1.3.6.1.4.1.91111.4.80.1.1.1.1.5
		tr1RSSI OBJECT-TYPE
			SYNTAX Integer32
			MAX-ACCESS read-only
			STATUS current
			DESCRIPTION
				"mV"
			::= { generalStatusEntry 5 }

		
		-- 1.3.6.1.4.1.91111.4.80.1.1.1.1.6
		tr2RSSI OBJECT-TYPE
			SYNTAX Integer32
			MAX-ACCESS read-only
			STATUS current
			DESCRIPTION
				"mV"
			::= { generalStatusEntry 6 }

		
		-- 1.3.6.1.4.1.91111.4.80.1.1.1.1.7
		xpicMode OBJECT-TYPE
			SYNTAX INTEGER
				{
				disabled(0),
				enabled(1)
				}
			MAX-ACCESS read-only
			STATUS current
			DESCRIPTION
				"Description."
			::= { generalStatusEntry 7 }

		
		-- 1.3.6.1.4.1.91111.4.80.1.1.1.1.8
		siteName OBJECT-TYPE
			SYNTAX OCTET STRING
			MAX-ACCESS read-only
			STATUS current
			DESCRIPTION
				"Description."
			::= { generalStatusEntry 8 }

		
		-- 1.3.6.1.4.1.91111.4.80.1.1.1.1.9
		systemUptime OBJECT-TYPE
			SYNTAX OCTET STRING
			MAX-ACCESS read-only
			STATUS current
			DESCRIPTION
				"Description."
			::= { generalStatusEntry 9 }

		
		-- 1.3.6.1.4.1.91111.4.80.1.1.1.1.10
		mcuUptime OBJECT-TYPE
			SYNTAX OCTET STRING
			MAX-ACCESS read-only
			STATUS current
			DESCRIPTION
				"Description."
			::= { generalStatusEntry 10 }

		
		-- 1.3.6.1.4.1.91111.4.80.1.1.1.1.11
		systemAlarm OBJECT-TYPE
			SYNTAX INTEGER
				{
				normal(0),
				alarm(1)
				}
			MAX-ACCESS read-only
			STATUS current
			DESCRIPTION
				"Description."
			::= { generalStatusEntry 11 }

		
		-- 1.3.6.1.4.1.91111.4.80.1.1.2
		channelStatusTable OBJECT-TYPE
			SYNTAX SEQUENCE OF ChannelStatusEntry
			MAX-ACCESS not-accessible
			STATUS current
			DESCRIPTION
				"Description."
			::= { radiolStatusObjects 2 }

		
		-- 1.3.6.1.4.1.91111.4.80.1.1.2.1
		channelStatusEntry OBJECT-TYPE
			SYNTAX ChannelStatusEntry
			MAX-ACCESS not-accessible
			STATUS current
			DESCRIPTION
				"Description."
			INDEX { channelStatusIndex }
			::= { channelStatusTable 1 }

		
		ChannelStatusEntry ::=
			SEQUENCE { 
				channelStatusIndex
					INTEGER,
				channelStatuslocation
					OCTET STRING,
				txFrequency
					Integer32,
				rxFrequency
					Integer32,
				trSpacing
					Integer32,
				trSide
					INTEGER,
				bandWidth
					Integer32,
				capacity
					Integer32,
				rsl
					RslTC,
				snr
					SnrTc,
				txPower
					Integer32,
				currentTxModulation
					ModulationType,
				currentRxModulation
					ModulationType,
				txMuteStatus
					INTEGER,
				modemLockStatus
					INTEGER
			 }

		-- 1.3.6.1.4.1.91111.4.80.1.1.2.1.1
		channelStatusIndex OBJECT-TYPE
			SYNTAX INTEGER (1..8)
			MAX-ACCESS read-only
			STATUS current
			DESCRIPTION
				"Description."
			::= { channelStatusEntry 1 }

		
		-- 1.3.6.1.4.1.91111.4.80.1.1.2.1.2
		channelStatuslocation OBJECT-TYPE
			SYNTAX OCTET STRING
			MAX-ACCESS read-only
			STATUS current
			DESCRIPTION
				"Description."
			::= { channelStatusEntry 2 }

		
		-- 1.3.6.1.4.1.91111.4.80.1.1.2.1.3
		txFrequency OBJECT-TYPE
			SYNTAX Integer32
			MAX-ACCESS read-only
			STATUS current
			DESCRIPTION
				"kHz."
			::= { channelStatusEntry 3 }

		
		-- 1.3.6.1.4.1.91111.4.80.1.1.2.1.4
		rxFrequency OBJECT-TYPE
			SYNTAX Integer32
			MAX-ACCESS read-only
			STATUS current
			DESCRIPTION
				"kHz."
			::= { channelStatusEntry 4 }

		
		-- 1.3.6.1.4.1.91111.4.80.1.1.2.1.5
		trSpacing OBJECT-TYPE
			SYNTAX Integer32
			MAX-ACCESS read-only
			STATUS current
			DESCRIPTION
				"kHz."
			::= { channelStatusEntry 5 }

		
		-- 1.3.6.1.4.1.91111.4.80.1.1.2.1.6
		trSide OBJECT-TYPE
			SYNTAX INTEGER
				{
				low(0),
				high(1)
				}
			MAX-ACCESS read-only
			STATUS current
			DESCRIPTION
				"Description."
			::= { channelStatusEntry 6 }

		
		-- 1.3.6.1.4.1.91111.4.80.1.1.2.1.7
		bandWidth OBJECT-TYPE
			SYNTAX Integer32
			MAX-ACCESS read-only
			STATUS current
			DESCRIPTION
				"kHz."
			::= { channelStatusEntry 7 }

		
		-- 1.3.6.1.4.1.91111.4.80.1.1.2.1.8
		capacity OBJECT-TYPE
			SYNTAX Integer32
			MAX-ACCESS read-only
			STATUS current
			DESCRIPTION
				"Kbps."
			::= { channelStatusEntry 8 }

		
		-- 1.3.6.1.4.1.91111.4.80.1.1.2.1.9
		rsl OBJECT-TYPE
			SYNTAX RslTC
			MAX-ACCESS read-only
			STATUS current
			DESCRIPTION
				"dBm. The real rsl value needs to be divided by 10. "
			::= { channelStatusEntry 9 }

		
		-- 1.3.6.1.4.1.91111.4.80.1.1.2.1.10
		snr OBJECT-TYPE
			SYNTAX SnrTc
			MAX-ACCESS read-only
			STATUS current
			DESCRIPTION
				"dB. The real value needs to be divided by 10."
			::= { channelStatusEntry 10 }

		
		-- 1.3.6.1.4.1.91111.4.80.1.1.2.1.11
		txPower OBJECT-TYPE
			SYNTAX Integer32
			MAX-ACCESS read-only
			STATUS current
			DESCRIPTION
				"dBm."
			::= { channelStatusEntry 11 }

		
		-- 1.3.6.1.4.1.91111.4.80.1.1.2.1.12
		currentTxModulation OBJECT-TYPE
			SYNTAX ModulationType
			MAX-ACCESS read-only
			STATUS current
			DESCRIPTION
				"Description."
			::= { channelStatusEntry 12 }

		
		-- 1.3.6.1.4.1.91111.4.80.1.1.2.1.13
		currentRxModulation OBJECT-TYPE
			SYNTAX ModulationType
			MAX-ACCESS read-only
			STATUS current
			DESCRIPTION
				"Description."
			::= { channelStatusEntry 13 }

		
		-- 1.3.6.1.4.1.91111.4.80.1.1.2.1.14
		txMuteStatus OBJECT-TYPE
			SYNTAX INTEGER
				{
				muteoff(0),
				muteon(1)
				}
			MAX-ACCESS read-only
			STATUS current
			DESCRIPTION
				"Description."
			::= { channelStatusEntry 14 }

		
		-- 1.3.6.1.4.1.91111.4.80.1.1.2.1.15
		modemLockStatus OBJECT-TYPE
			SYNTAX INTEGER
				{
				unlocked(0),
				locked(1)
				}
			MAX-ACCESS read-only
			STATUS current
			DESCRIPTION
				"Description."
			::= { channelStatusEntry 15 }

		
		-- 1.3.6.1.4.1.91111.4.80.1.3
		radiolStatusGroup OBJECT IDENTIFIER ::= { radioStatus 3 }

		
		-- 1.3.6.1.4.1.91111.4.80.1.3.1
		generalStatusGroup OBJECT-GROUP
			OBJECTS { generalStatusIndex, ipStatus, temperture, tr1RSSI, tr2RSSI, 
				xpicMode, siteName, systemUptime, mcuUptime, systemAlarm, 
				generalStatuslocation }
			STATUS current
			DESCRIPTION 
				"Description."
			::= { radiolStatusGroup 1 }

		
		-- 1.3.6.1.4.1.91111.4.80.1.3.2
		channelStatusGroup OBJECT-GROUP
			OBJECTS { channelStatusIndex, txFrequency, rxFrequency, trSpacing, trSide, 
				bandWidth, capacity, rsl, snr, currentRxModulation, 
				currentTxModulation, txPower, channelStatuslocation, txMuteStatus, modemLockStatus
				 }
			STATUS current
			DESCRIPTION 
				"Description."
			::= { radiolStatusGroup 2 }

		
	
	END

--
-- RADIO-DUMONTSTATUS-MIB.my
--
